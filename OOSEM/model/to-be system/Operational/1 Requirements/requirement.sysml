package {
    package Operational {
        package Requirements {
            requirement ESSMIssionRequirement {
                doc /*
                     * Enhance security of life and property by providing emergency responseTime 
                     * for single-family residence, multi-family residence, and small business,
                     * to theft, burglary, fire, and health and safety.
                     */
                requirement IntruderEmergencyResponse;
                requirement FireEmergencyResponse;
                requirement HealthAndSafetyEmergencyResponse;
            }
        }
    }
}
